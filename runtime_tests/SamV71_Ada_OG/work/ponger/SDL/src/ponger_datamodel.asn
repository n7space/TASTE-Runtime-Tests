Ponger-Datamodel DEFINITIONS ::=
BEGIN
--  This file was generated automatically by OpenGEODE
IMPORTS
   MyInteger FROM SAMV71-ADA-OG-DATAVIEW
   T-Int32, T-UInt32, T-Int8, T-UInt8, T-Boolean, T-Null-Record FROM TASTE-BasicTypes
   PID-Range, PID FROM System-Dataview;

Ponger-States ::= ENUMERATED {wait}

Ponger-Context ::= SEQUENCE {
   state Ponger-States,
   init-done BOOLEAN,
   sender PID,
   counter MyInteger,
   pingarg MyInteger
}

END
